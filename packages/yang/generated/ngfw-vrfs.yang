module ngfw-vrfs {
  yang-version 1.1;
  namespace "urn:ngfw:vrfs";
  prefix ngfw-vrfs;

  organization "NGFW";
  contact "https://ngfw.dev";
  description "Configuration of the 'vrfs' domain, generated from the NGFW Zod schema (F-restconf-yang).";

  revision 2026-01-01 {
    description "Generated from the NGFW schema.";
  }

  list vrfs {
    key "name";
    leaf name {
      type string;
      description "The map key.";
    }
    description "VRF / FIB tables keyed by name.";
    leaf id {
      type uint32 {
        range "0..4294967295";
      }
      mandatory true;
      description "Engine FIB table id (0 is the default VRF)";
    }
    leaf description {
      type string {
        // pattern dropped: not XSD-expressible
        length "0..255";
      }
    }
    list sourceSelect {
      key "interface prefix";
      description "route packets from these source prefixes, arriving on these interfaces, in this VRF";
      leaf prefix {
        type union {
          type string {
            pattern "((25[0-5]|2[0-4][0-9]|1[0-9][0-9]|[1-9][0-9]|[0-9])\\.){3}(25[0-5]|2[0-4][0-9]|1[0-9][0-9]|[1-9][0-9]|[0-9])/([0-9]|[1-2][0-9]|3[0-2])";
          }
          type string {
            pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))/(12[0-8]|1[01][0-9]|[1-9]?[0-9])";
          }
        }
        mandatory true;
        description "packets whose source address is in this prefix, e.g. 10.20.0.0/16";
      }
      leaf interface {
        type string {
          pattern "[A-Za-z][A-Za-z0-9_-]*(/[0-9a-fA-F]+)*(\\.[0-9]+)?";
          length "1..63";
        }
        mandatory true;
        description "interface the packets arrive on";
      }
    }
    list proxyArpRanges {
      key "low high";
      description "IPv4 ranges answered by proxy ARP on interfaces of this VRF that enable it";
      leaf low {
        type string {
          pattern "((25[0-5]|2[0-4][0-9]|1[0-9][0-9]|[1-9][0-9]|[0-9])\\.){3}(25[0-5]|2[0-4][0-9]|1[0-9][0-9]|[1-9][0-9]|[0-9])";
        }
        mandatory true;
      }
      leaf high {
        type string {
          pattern "((25[0-5]|2[0-4][0-9]|1[0-9][0-9]|[1-9][0-9]|[0-9])\\.){3}(25[0-5]|2[0-4][0-9]|1[0-9][0-9]|[1-9][0-9]|[0-9])";
        }
        mandatory true;
      }
    }
  }
}
