module vrx-dataplane {
  yang-version 1.1;
  namespace "urn:vrx:dataplane";
  prefix vrx-dataplane;

  organization "VRX";
  contact "https://vrx.dev";
  description "Configuration of the 'dataplane' domain, generated from the VRX Zod schema (F-restconf-yang).";

  revision 2026-01-01 {
    description "Generated from the VRX schema.";
  }

  container dataplane {
    description "VPP data-plane tuning: worker threads, RX queues, hugepages, PCI whitelist and core placement.";
    leaf workers {
      type uint32 {
        range "0..255";
      }
      description "number of engine worker threads; 0 = run the graph on the main thread only";
    }
    leaf-list corelist {
      type uint32 {
        range "0..1023";
      }
      description "CPU ids pinned to worker threads (corelist-workers); when set, `workers` must equal its length";
    }
    leaf mainCore {
      type uint32 {
        range "0..1023";
      }
      description "CPU id of the engine main thread (must not be a worker core)";
    }
    leaf rxQueues {
      type uint32 {
        range "1..256";
      }
      description "dpdk { dev default { num-rx-queues N } }";
    }
    leaf txQueues {
      type uint32 {
        range "1..256";
      }
      description "dpdk { dev default { num-tx-queues N } }";
    }
    leaf hugepagesGb {
      type uint32 {
        range "1..1024";
      }
      description "total 2 MB hugepage memory reserved for the data plane";
    }
    leaf-list pciWhitelist {
      type string {
        pattern "[0-9a-fA-F]{4}:[0-9a-fA-F]{2}:[0-9a-fA-F]{2}\\.[0-7]";
      }
      description "NICs handed to DPDK (dpdk { dev 0000:0b:00.0 }); empty = no DPDK devices";
    }
    leaf-list managementPci {
      type string {
        pattern "[0-9a-fA-F]{4}:[0-9a-fA-F]{2}:[0-9a-fA-F]{2}\\.[0-7]";
      }
      description "PCI addresses of the management NIC(s): always blacklisted, never handed to DPDK (the generator also protects the NIC it detects on the host)";
    }
    list devices {
      key "name";
      leaf name {
        type string;
        description "The map key.";
      }
      description "NICs handed to DPDK keyed by PCI address, each with its logical interface name (dpdk { dev <pci> { name lan } })";
      leaf name {
        type string {
          pattern "[a-z]([a-z0-9_-]{0,13}[a-z0-9])?";
        }
        description "dpdk { dev <pci> { name <logical> } } — the interface name used everywhere else in the configuration";
      }
      leaf rxQueues {
        type uint32 {
          range "1..256";
        }
      }
      leaf txQueues {
        type uint32 {
          range "1..256";
        }
      }
      leaf rxDesc {
        type uint32 {
          range "64..16384";
        }
        description "power of two";
      }
      leaf txDesc {
        type uint32 {
          range "64..16384";
        }
        description "power of two";
      }
    }
    leaf buffersPerNuma {
      type uint32 {
        range "1024..4194304";
      }
      description "buffers { buffers-per-numa N }; must fit in the hugepage reservation";
    }
    container plugins {
      description "plugins { plugin <file> { enable|disable } }. Present = authoritative: exactly these switches are rendered (true = enable, false = disable). Absent = the switches of the current start-up configuration are kept (D-084)";
      list switches {
        key "name";
        leaf name {
          type string;
          description "The map key.";
        }
        description "plugin file → true (enable) / false (disable)";
      }
    }
  }
}
