module vrx-vpn {
  yang-version 1.1;
  namespace "urn:vrx:vpn";
  prefix vrx-vpn;

  organization "VRX";
  contact "https://vrx.dev";
  description "Configuration of the 'vpn' domain, generated from the VRX Zod schema (F-restconf-yang).";

  revision 2026-01-01 {
    description "Generated from the VRX schema.";
  }

  container vpn {
    description "IPsec (strongSwan / native IKEv2), WireGuard, PKI and remote-access VPN.";
    container ipsec {
      container settings {
        leaf cryptoEngine {
          type enumeration {
            enum "auto";
            enum "native";
            enum "ipsecmb";
            enum "openssl";
          }
          default "auto";
        }
        leaf asyncCrypto {
          type boolean;
          default "false";
          description "Dedicated crypto workers / QAT offload (D6.1)";
        }
      }
      list proposals {
        key "name";
        leaf name {
          type string;
          description "The map key.";
        }
        leaf description {
          type string {
            // pattern dropped: not XSD-expressible
            length "0..255";
          }
        }
        container ike {
          leaf encr {
            type enumeration {
              enum "aes128";
              enum "aes192";
              enum "aes256";
              enum "aes128ctr";
              enum "aes256ctr";
              enum "aes128gcm8";
              enum "aes128gcm12";
              enum "aes128gcm16";
              enum "aes192gcm16";
              enum "aes256gcm8";
              enum "aes256gcm12";
              enum "aes256gcm16";
              enum "chacha20poly1305";
              enum "3des";
            }
            mandatory true;
          }
          leaf integ {
            type enumeration {
              enum "sha1";
              enum "sha256";
              enum "sha384";
              enum "sha512";
              enum "md5";
              enum "aesxcbc";
              enum "aescmac";
            }
          }
          leaf prf {
            type enumeration {
              enum "prfsha1";
              enum "prfsha256";
              enum "prfsha384";
              enum "prfsha512";
              enum "prfmd5";
              enum "prfaesxcbc";
              enum "prfaescmac";
            }
            description "Defaults to the PRF matching the integrity algorithm";
          }
          leaf dh {
            type enumeration {
              enum "modp768";
              enum "modp1024";
              enum "modp1536";
              enum "modp2048";
              enum "modp3072";
              enum "modp4096";
              enum "modp6144";
              enum "modp8192";
              enum "ecp256";
              enum "ecp384";
              enum "ecp521";
              enum "modp1024s160";
              enum "modp2048s224";
              enum "modp2048s256";
              enum "ecp192";
              enum "ecp224";
              enum "curve25519";
              enum "curve448";
            }
            mandatory true;
          }
        }
        container esp {
          leaf encr {
            type enumeration {
              enum "aes128";
              enum "aes192";
              enum "aes256";
              enum "aes128ctr";
              enum "aes256ctr";
              enum "aes128gcm8";
              enum "aes128gcm12";
              enum "aes128gcm16";
              enum "aes192gcm16";
              enum "aes256gcm8";
              enum "aes256gcm12";
              enum "aes256gcm16";
              enum "chacha20poly1305";
              enum "3des";
              enum "null";
            }
            mandatory true;
          }
          leaf integ {
            type enumeration {
              enum "sha1";
              enum "sha256";
              enum "sha384";
              enum "sha512";
              enum "md5";
              enum "aesxcbc";
              enum "aescmac";
            }
          }
          leaf dh {
            type enumeration {
              enum "modp768";
              enum "modp1024";
              enum "modp1536";
              enum "modp2048";
              enum "modp3072";
              enum "modp4096";
              enum "modp6144";
              enum "modp8192";
              enum "ecp256";
              enum "ecp384";
              enum "ecp521";
              enum "modp1024s160";
              enum "modp2048s224";
              enum "modp2048s256";
              enum "ecp192";
              enum "ecp224";
              enum "curve25519";
              enum "curve448";
            }
            description "Perfect forward secrecy for CHILD_SA rekeying; omit to disable";
          }
        }
      }
      list tunnels {
        key "name";
        leaf name {
          type string;
          description "The map key.";
        }
        leaf enabled {
          type boolean;
          default "true";
        }
        leaf description {
          type string {
            // pattern dropped: not XSD-expressible
            length "0..255";
          }
        }
        leaf engine {
          type enumeration {
            enum "vpp-ikev2";
          }
          default "vpp-ikev2";
          description "Route-based IPsec with native IKEv2";
        }
        leaf ikeVersion {
          type union {
            type uint32 {
              range "1";
            }
            type uint32 {
              range "2";
            }
          }
          default "2";
        }
        leaf mode {
          type enumeration {
            enum "tunnel";
            enum "transport";
          }
          default "tunnel";
        }
        leaf protocol {
          type enumeration {
            enum "esp";
            enum "ah";
          }
          default "esp";
        }
        leaf localAddr {
          type union {
            type string {
              pattern "((25[0-5]|2[0-4][0-9]|1[0-9][0-9]|[1-9][0-9]|[0-9])\\.){3}(25[0-5]|2[0-4][0-9]|1[0-9][0-9]|[1-9][0-9]|[0-9])";
            }
            type string {
              pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))";
            }
          }
          mandatory true;
          description "Must be configured on an interface in the underlay VRF";
        }
        leaf remoteAddr {
          type union {
            type union {
              type string {
                pattern "((25[0-5]|2[0-4][0-9]|1[0-9][0-9]|[1-9][0-9]|[0-9])\\.){3}(25[0-5]|2[0-4][0-9]|1[0-9][0-9]|[1-9][0-9]|[0-9])";
              }
              type string {
                pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))";
              }
            }
            type string {
              pattern "[A-Za-z0-9]([A-Za-z0-9-]{0,61}[A-Za-z0-9])?(\\.[A-Za-z0-9]([A-Za-z0-9-]{0,61}[A-Za-z0-9])?)*";
              length "1..253";
            }
            type string;
          }
          mandatory true;
          description "IP, hostname, or %any for a responder-only tunnel";
        }
        leaf localId {
          type string {
            pattern "[!#-~][ !#-~]*";
            length "1..255";
          }
          description "FQDN, e-mail, IP address, @keyid or X.509 DN";
        }
        leaf remoteId {
          type string {
            pattern "[!#-~][ !#-~]*";
            length "1..255";
          }
          description "FQDN, e-mail, IP address, @keyid or X.509 DN";
        }
        leaf auth {
          type string;
          mandatory true;
        }
        leaf proposal {
          type string {
            pattern "[A-Za-z0-9][A-Za-z0-9_.-]*";
            length "1..63";
          }
          mandatory true;
          description "Name in vpn.ipsec.proposals";
        }
        leaf-list localTs {
          type union {
            type string {
              pattern "((25[0-5]|2[0-4][0-9]|1[0-9][0-9]|[1-9][0-9]|[0-9])\\.){3}(25[0-5]|2[0-4][0-9]|1[0-9][0-9]|[1-9][0-9]|[0-9])/([0-9]|[1-2][0-9]|3[0-2])";
            }
            type string {
              pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))/(12[0-8]|1[01][0-9]|[1-9]?[0-9])";
            }
          }
          description "One local network; empty uses the wildcard selector of the address family";
        }
        leaf-list remoteTs {
          type union {
            type string {
              pattern "((25[0-5]|2[0-4][0-9]|1[0-9][0-9]|[1-9][0-9]|[0-9])\\.){3}(25[0-5]|2[0-4][0-9]|1[0-9][0-9]|[1-9][0-9]|[0-9])/([0-9]|[1-2][0-9]|3[0-2])";
            }
            type string {
              pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))/(12[0-8]|1[01][0-9]|[1-9]?[0-9])";
            }
          }
        }
        leaf natT {
          type boolean;
          default "true";
        }
        leaf mobike {
          type boolean;
          description "IKEv2 only; unset = strongSwan default";
        }
        leaf fragmentation {
          type enumeration {
            enum "yes";
            enum "no";
            enum "force";
            enum "accept";
          }
        }
        container rekey {
          leaf espSec {
            type uint32 {
              range "60..604800";
            }
            default "3600";
          }
          leaf espBytes {
            type uint64 {
              range "1..9007199254740991";
            }
          }
        }
        leaf startAction {
          type enumeration {
            enum "none";
            enum "start";
            enum "trap";
          }
          default "none";
        }
        leaf closeAction {
          type enumeration {
            enum "none";
            enum "start";
            enum "trap";
          }
          default "none";
        }
        leaf vrf {
          type string {
            pattern "[A-Za-z0-9][A-Za-z0-9_.-]*";
            length "1..63";
          }
          default "default";
          description "Overlay: FIB the traffic selectors apply to / the protected IPIP interface belongs to";
        }
        leaf underlayVrf {
          type string {
            pattern "[A-Za-z0-9][A-Za-z0-9_.-]*";
            length "1..63";
          }
          default "default";
          description "FIB IKE and ESP run in: localAddr must be configured on an interface in it; remoteAddr is reached through it";
        }
        container routeBased {
          leaf ipipInterface {
            type string {
              pattern "[A-Za-z0-9][A-Za-z0-9_.-]*";
              length "1..63";
            }
            mandatory true;
            description "Name in tunnels.ipip; the tunnel is protected (ipsec_tunnel_protect) and traffic is steered by routes";
          }
        }
        leaf esn {
          type boolean;
          default "false";
        }
        leaf antiReplay {
          type boolean;
          default "true";
        }
      }
    }
    container wireguard {
      list interfaces {
        key "name";
        leaf name {
          type string;
          description "The map key.";
        }
        leaf enabled {
          type boolean;
          default "true";
        }
        leaf description {
          type string {
            // pattern dropped: not XSD-expressible
            length "0..255";
          }
        }
        leaf instance {
          type uint32 {
            range "0..4294967295";
          }
          mandatory true;
          description "Engine interface name is wg<instance>";
        }
        leaf vrf {
          type string {
            pattern "[A-Za-z0-9][A-Za-z0-9_.-]*";
            length "1..63";
          }
          default "default";
          description "Routing table this object belongs to (first-class, never implicit)";
        }
        leaf underlayVrf {
          type string {
            pattern "[A-Za-z0-9][A-Za-z0-9_.-]*";
            length "1..63";
          }
          default "default";
          description "VRF of the listen address / peer endpoints";
        }
        leaf listenAddress {
          type union {
            type string {
              pattern "((25[0-5]|2[0-4][0-9]|1[0-9][0-9]|[1-9][0-9]|[0-9])\\.){3}(25[0-5]|2[0-4][0-9]|1[0-9][0-9]|[1-9][0-9]|[0-9])";
            }
            type string {
              pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))";
            }
          }
          mandatory true;
          description "Source address of the tunnel; must be configured on an interface in the underlay VRF";
        }
        leaf listenPort {
          type uint32 {
            range "1..65535";
          }
          default "51820";
        }
        leaf privateKeyRef {
          type string {
            pattern "(key)/[A-Za-z0-9][A-Za-z0-9_.-]{0,62}";
            length "1..127";
          }
          mandatory true;
          description "Reference to a stored secret of kind key. The secret itself is never part of the configuration.";
        }
        leaf-list address {
          type union {
            type string {
              pattern "((25[0-5]|2[0-4][0-9]|1[0-9][0-9]|[1-9][0-9]|[0-9])\\.){3}(25[0-5]|2[0-4][0-9]|1[0-9][0-9]|[1-9][0-9]|[0-9])/([0-9]|[1-2][0-9]|3[0-2])";
            }
            type string {
              pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))/(12[0-8]|1[01][0-9]|[1-9]?[0-9])";
            }
          }
        }
        leaf mtu {
          type uint32 {
            range "68..9216";
          }
          default "1420";
        }
        list peers {
          key "name";
          leaf name {
            type string;
            description "The map key.";
          }
          leaf description {
            type string {
              // pattern dropped: not XSD-expressible
              length "0..255";
            }
          }
          leaf publicKey {
            type string {
              pattern "[A-Za-z0-9+/]{42}[AEIMQUYcgkosw048]=";
              length "44..44";
            }
            mandatory true;
          }
          leaf presharedKeyRef {
            type string {
              pattern "(psk)/[A-Za-z0-9][A-Za-z0-9_.-]{0,62}";
              length "1..127";
            }
            description "Reference to a stored secret of kind psk. The secret itself is never part of the configuration.";
          }
          container endpoint {
            description "Omit for peers that always initiate";
            leaf address {
              type union {
                type union {
                  type string {
                    pattern "((25[0-5]|2[0-4][0-9]|1[0-9][0-9]|[1-9][0-9]|[0-9])\\.){3}(25[0-5]|2[0-4][0-9]|1[0-9][0-9]|[1-9][0-9]|[0-9])";
                  }
                  type string {
                    pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))";
                  }
                }
                type string {
                  pattern "[A-Za-z0-9]([A-Za-z0-9-]{0,61}[A-Za-z0-9])?(\\.[A-Za-z0-9]([A-Za-z0-9-]{0,61}[A-Za-z0-9])?)*";
                  length "1..253";
                }
              }
              mandatory true;
            }
            leaf port {
              type uint32 {
                range "1..65535";
              }
              mandatory true;
            }
          }
          leaf-list allowedIps {
            type union {
              type string {
                pattern "((25[0-5]|2[0-4][0-9]|1[0-9][0-9]|[1-9][0-9]|[0-9])\\.){3}(25[0-5]|2[0-4][0-9]|1[0-9][0-9]|[1-9][0-9]|[0-9])/([0-9]|[1-2][0-9]|3[0-2])";
              }
              type string {
                pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))/(12[0-8]|1[01][0-9]|[1-9]?[0-9])";
              }
            }
            description "Cryptokey routing: prefixes accepted from / routed to this peer";
          }
          leaf persistentKeepaliveSec {
            type uint32 {
              range "0..65535";
            }
            default "0";
            description "0 disables";
          }
        }
        leaf routeAllowedIps {
          type boolean;
          default "false";
          description "Install a route via this interface for every allowed IP of its peers (TNSR does not; F-wireguard)";
        }
      }
    }
    container pki {
      list cas {
        key "name";
        leaf name {
          type string;
          description "The map key.";
        }
        leaf description {
          type string {
            // pattern dropped: not XSD-expressible
            length "0..255";
          }
        }
        leaf certificateRef {
          type string {
            pattern "(cert)/[A-Za-z0-9][A-Za-z0-9_.-]{0,62}";
            length "1..127";
          }
          mandatory true;
          description "PEM stored through POST /api/v1/secrets (kind cert)";
        }
        container crl {
          leaf url {
            type string {
              length "0..2048";
            }
          }
          leaf refreshIntervalSec {
            type uint32 {
              range "300..2592000";
            }
            default "86400";
          }
        }
        leaf ocspUrl {
          type string {
            length "0..2048";
          }
        }
        container keySpec {
          description "How the CA key pair was generated (POST /api/v1/actions/pki/ca)";
          leaf type {
            type enumeration {
              enum "ecdsa";
              enum "rsa";
            }
            default "ecdsa";
          }
          leaf curve {
            type enumeration {
              enum "p256";
              enum "p384";
            }
            description "ECDSA only (default p256)";
          }
          leaf bits {
            type union {
              type uint32 {
                range "2048";
              }
              type uint32 {
                range "3072";
              }
              type uint32 {
                range "4096";
              }
            }
            description "RSA only (default 2048)";
          }
        }
        container issued {
          description "Recorded by the PKI actions";
          leaf subject {
            type string {
              length "1..1024";
            }
            mandatory true;
          }
          leaf issuer {
            type string {
              length "1..1024";
            }
            mandatory true;
          }
          leaf serial {
            type string {
              pattern "[0-9A-F]{2}(:[0-9A-F]{2}){0,31}";
              length "0..95";
            }
            mandatory true;
          }
          leaf notBefore {
            type string {
              pattern "((\\d\\d[2468][048]|\\d\\d[13579][26]|\\d\\d0[48]|[02468][048]00|[13579][26]00)-02-29|\\d{4}-((0[13578]|1[02])-(0[1-9]|[12]\\d|3[01])|(0[469]|11)-(0[1-9]|[12]\\d|30)|(02)-(0[1-9]|1\\d|2[0-8])))T(([01]\\d|2[0-3]):[0-5]\\d:[0-5]\\d(\\.\\d+)?(Z|([+-]([01]\\d|2[0-3]):[0-5]\\d)))";
            }
            mandatory true;
          }
          leaf notAfter {
            type string {
              pattern "((\\d\\d[2468][048]|\\d\\d[13579][26]|\\d\\d0[48]|[02468][048]00|[13579][26]00)-02-29|\\d{4}-((0[13578]|1[02])-(0[1-9]|[12]\\d|3[01])|(0[469]|11)-(0[1-9]|[12]\\d|30)|(02)-(0[1-9]|1\\d|2[0-8])))T(([01]\\d|2[0-3]):[0-5]\\d:[0-5]\\d(\\.\\d+)?(Z|([+-]([01]\\d|2[0-3]):[0-5]\\d)))";
            }
            mandatory true;
          }
          leaf fingerprint {
            type string {
              pattern "[0-9A-F]{2}(:[0-9A-F]{2}){0,31}";
              length "95..95";
            }
            mandatory true;
          }
          leaf ca {
            type boolean;
          }
        }
      }
      list certificates {
        key "name";
        leaf name {
          type string;
          description "The map key.";
        }
        leaf description {
          type string {
            // pattern dropped: not XSD-expressible
            length "0..255";
          }
        }
        leaf certificateRef {
          type string {
            pattern "(cert)/[A-Za-z0-9][A-Za-z0-9_.-]{0,62}";
            length "1..127";
          }
          description "Reference to a stored secret of kind cert. The secret itself is never part of the configuration.";
        }
        leaf privateKeyRef {
          type string {
            pattern "(key)/[A-Za-z0-9][A-Za-z0-9_.-]{0,62}";
            length "1..127";
          }
          mandatory true;
          description "Reference to a stored secret of kind key. The secret itself is never part of the configuration.";
        }
        leaf ca {
          type string {
            pattern "[A-Za-z0-9][A-Za-z0-9_.-]*";
            length "1..63";
          }
          description "Name in vpn.pki.cas";
        }
        container acme {
          description "Certificate is obtained/renewed automatically";
          leaf directoryUrl {
            type string {
              length "0..2048";
            }
            default "https://acme-v02.api.letsencrypt.org/directory";
          }
          leaf-list domains {
            type string {
              pattern "[A-Za-z0-9]([A-Za-z0-9-]{0,61}[A-Za-z0-9])?(\\.[A-Za-z0-9]([A-Za-z0-9-]{0,61}[A-Za-z0-9])?)*";
              length "1..253";
            }
          }
          leaf email {
            type string {
              pattern "([A-Za-z0-9_'+\\-]+\\.)*[A-Za-z0-9_'+\\-]*[A-Za-z0-9_+-]@([A-Za-z0-9][A-Za-z0-9\\-]*\\.)+[A-Za-z]{2,}";
            }
          }
          leaf challenge {
            type enumeration {
              enum "http-01";
              enum "dns-01";
            }
            default "http-01";
          }
        }
        leaf expiryAlertDays {
          type uint32 {
            range "1..365";
          }
          default "30";
        }
        container csr {
          description "Subject, SANs and key of the request (POST /api/v1/actions/pki/csr)";
          leaf subject {
            type string {
              // pattern dropped: not XSD-expressible
              length "4..1024";
            }
            mandatory true;
          }
          leaf-list san {
            type union {
              type union {
                type string {
                  pattern "((25[0-5]|2[0-4][0-9]|1[0-9][0-9]|[1-9][0-9]|[0-9])\\.){3}(25[0-5]|2[0-4][0-9]|1[0-9][0-9]|[1-9][0-9]|[0-9])";
                }
                type string {
                  pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))";
                }
              }
              type string {
                pattern "([A-Za-z0-9_'+\\-]+\\.)*[A-Za-z0-9_'+\\-]*[A-Za-z0-9_+-]@([A-Za-z0-9][A-Za-z0-9\\-]*\\.)+[A-Za-z]{2,}";
              }
              type string {
                pattern "(\\*\\.)?[A-Za-z0-9]([A-Za-z0-9-]{0,61}[A-Za-z0-9])?(\\.[A-Za-z0-9]([A-Za-z0-9-]{0,61}[A-Za-z0-9])?)*";
                length "1..253";
              }
            }
            description "DNS names, IP addresses or e-mail addresses";
          }
          container keySpec {
            leaf type {
              type enumeration {
                enum "ecdsa";
                enum "rsa";
              }
              default "ecdsa";
            }
            leaf curve {
              type enumeration {
                enum "p256";
                enum "p384";
              }
              description "ECDSA only (default p256)";
            }
            leaf bits {
              type union {
                type uint32 {
                  range "2048";
                }
                type uint32 {
                  range "3072";
                }
                type uint32 {
                  range "4096";
                }
              }
              description "RSA only (default 2048)";
            }
          }
        }
        container issued {
          description "Recorded by the PKI actions";
          leaf subject {
            type string {
              length "1..1024";
            }
            mandatory true;
          }
          leaf issuer {
            type string {
              length "1..1024";
            }
            mandatory true;
          }
          leaf serial {
            type string {
              pattern "[0-9A-F]{2}(:[0-9A-F]{2}){0,31}";
              length "0..95";
            }
            mandatory true;
          }
          leaf notBefore {
            type string {
              pattern "((\\d\\d[2468][048]|\\d\\d[13579][26]|\\d\\d0[48]|[02468][048]00|[13579][26]00)-02-29|\\d{4}-((0[13578]|1[02])-(0[1-9]|[12]\\d|3[01])|(0[469]|11)-(0[1-9]|[12]\\d|30)|(02)-(0[1-9]|1\\d|2[0-8])))T(([01]\\d|2[0-3]):[0-5]\\d:[0-5]\\d(\\.\\d+)?(Z|([+-]([01]\\d|2[0-3]):[0-5]\\d)))";
            }
            mandatory true;
          }
          leaf notAfter {
            type string {
              pattern "((\\d\\d[2468][048]|\\d\\d[13579][26]|\\d\\d0[48]|[02468][048]00|[13579][26]00)-02-29|\\d{4}-((0[13578]|1[02])-(0[1-9]|[12]\\d|3[01])|(0[469]|11)-(0[1-9]|[12]\\d|30)|(02)-(0[1-9]|1\\d|2[0-8])))T(([01]\\d|2[0-3]):[0-5]\\d:[0-5]\\d(\\.\\d+)?(Z|([+-]([01]\\d|2[0-3]):[0-5]\\d)))";
            }
            mandatory true;
          }
          leaf fingerprint {
            type string {
              pattern "[0-9A-F]{2}(:[0-9A-F]{2}){0,31}";
              length "95..95";
            }
            mandatory true;
          }
          leaf ca {
            type boolean;
          }
        }
      }
      container hsm {
        leaf enabled {
          type boolean;
          default "false";
        }
        leaf module {
          type string {
            pattern "/[A-Za-z0-9_.+/-]*";
            length "0..255";
          }
          mandatory true;
        }
        leaf tokenLabel {
          type string {
            length "1..32";
          }
        }
        leaf pinRef {
          type string {
            pattern "(password)/[A-Za-z0-9][A-Za-z0-9_.-]{0,62}";
            length "1..127";
          }
          description "Reference to a stored secret of kind password. The secret itself is never part of the configuration.";
        }
      }
    }
    list remoteAccess {
      key "name";
      leaf name {
        type string;
        description "The map key.";
      }
      leaf enabled {
        type boolean;
        default "true";
      }
      leaf description {
        type string {
          // pattern dropped: not XSD-expressible
          length "0..255";
        }
      }
      leaf localAddr {
        type union {
          type string {
            pattern "((25[0-5]|2[0-4][0-9]|1[0-9][0-9]|[1-9][0-9]|[0-9])\\.){3}(25[0-5]|2[0-4][0-9]|1[0-9][0-9]|[1-9][0-9]|[0-9])";
          }
          type string {
            pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))";
          }
        }
        mandatory true;
        description "Must be configured on an interface in the underlay VRF";
      }
      leaf localId {
        type string {
          pattern "[!#-~][ !#-~]*";
          length "1..255";
        }
        description "FQDN, e-mail, IP address, @keyid or X.509 DN";
      }
      leaf vrf {
        type string {
          pattern "[A-Za-z0-9][A-Za-z0-9_.-]*";
          length "1..63";
        }
        default "default";
        description "Overlay: FIB the client pools are routed in";
      }
      leaf underlayVrf {
        type string {
          pattern "[A-Za-z0-9][A-Za-z0-9_.-]*";
          length "1..63";
        }
        default "default";
        description "FIB IKE and ESP run in (localAddr, client endpoints)";
      }
      leaf auth {
        type enumeration {
          enum "eap-mschapv2";
          enum "eap-tls";
          enum "eap-radius";
          enum "pubkey";
        }
        default "eap-mschapv2";
      }
      leaf certificate {
        type string {
          pattern "[A-Za-z0-9][A-Za-z0-9_.-]*";
          length "1..63";
        }
        mandatory true;
        description "Name in vpn.pki.certificates";
      }
      leaf clientCa {
        type string {
          pattern "[A-Za-z0-9][A-Za-z0-9_.-]*";
          length "1..63";
        }
        description "Name in vpn.pki.cas (eap-tls / pubkey)";
      }
      leaf proposal {
        type string {
          pattern "[A-Za-z0-9][A-Za-z0-9_.-]*";
          length "1..63";
        }
        mandatory true;
        description "Name in vpn.ipsec.proposals";
      }
      list pools {
        // keyless: no itemKey meta — config lists need a key (documented deviation, RESTCONF orders by index)
        ordered-by user;
        leaf name {
          type string {
            pattern "[A-Za-z0-9][A-Za-z0-9_.-]*";
            length "1..63";
          }
          mandatory true;
        }
        leaf prefix {
          type union {
            type string {
              pattern "((25[0-5]|2[0-4][0-9]|1[0-9][0-9]|[1-9][0-9]|[0-9])\\.){3}(25[0-5]|2[0-4][0-9]|1[0-9][0-9]|[1-9][0-9]|[0-9])/([0-9]|[1-2][0-9]|3[0-2])";
            }
            type string {
              pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))/(12[0-8]|1[01][0-9]|[1-9]?[0-9])";
            }
          }
          mandatory true;
        }
        leaf-list dns {
          type union {
            type string {
              pattern "((25[0-5]|2[0-4][0-9]|1[0-9][0-9]|[1-9][0-9]|[0-9])\\.){3}(25[0-5]|2[0-4][0-9]|1[0-9][0-9]|[1-9][0-9]|[0-9])";
            }
            type string {
              pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))";
            }
          }
        }
      }
      leaf-list splitTunnel {
        type union {
          type string {
            pattern "((25[0-5]|2[0-4][0-9]|1[0-9][0-9]|[1-9][0-9]|[0-9])\\.){3}(25[0-5]|2[0-4][0-9]|1[0-9][0-9]|[1-9][0-9]|[0-9])/([0-9]|[1-2][0-9]|3[0-2])";
          }
          type string {
            pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))/(12[0-8]|1[01][0-9]|[1-9]?[0-9])";
          }
        }
        description "Empty = full tunnel (0.0.0.0/0, ::/0)";
      }
      list users {
        // keyless: no itemKey meta — config lists need a key (documented deviation, RESTCONF orders by index)
        ordered-by user;
        leaf username {
          type string {
            pattern "[A-Za-z0-9][A-Za-z0-9_.@-]*";
            length "1..64";
          }
          mandatory true;
        }
        leaf passwordRef {
          type string {
            pattern "(password)/[A-Za-z0-9][A-Za-z0-9_.-]{0,62}";
            length "1..127";
          }
          mandatory true;
          description "Reference to a stored secret of kind password. The secret itself is never part of the configuration.";
        }
      }
      container radius {
        list servers {
          // keyless: no itemKey meta — config lists need a key (documented deviation, RESTCONF orders by index)
          ordered-by user;
          leaf address {
            type union {
              type union {
                type string {
                  pattern "((25[0-5]|2[0-4][0-9]|1[0-9][0-9]|[1-9][0-9]|[0-9])\\.){3}(25[0-5]|2[0-4][0-9]|1[0-9][0-9]|[1-9][0-9]|[0-9])";
                }
                type string {
                  pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))";
                }
              }
              type string {
                pattern "[A-Za-z0-9]([A-Za-z0-9-]{0,61}[A-Za-z0-9])?(\\.[A-Za-z0-9]([A-Za-z0-9-]{0,61}[A-Za-z0-9])?)*";
                length "1..253";
              }
            }
            mandatory true;
          }
          leaf port {
            type uint32 {
              range "1..65535";
            }
            default "1812";
          }
          leaf secretRef {
            type string {
              pattern "(psk)/[A-Za-z0-9][A-Za-z0-9_.-]{0,62}";
              length "1..127";
            }
            mandatory true;
            description "Reference to a stored secret of kind psk. The secret itself is never part of the configuration.";
          }
        }
      }
      container dpd {
        leaf enabled {
          type boolean;
          default "true";
        }
        leaf delaySec {
          type uint32 {
            range "1..86400";
          }
          default "30";
        }
        leaf timeoutSec {
          type uint32 {
            range "1..86400";
          }
          default "150";
          description "IKEv1 only; IKEv2 uses the retransmission timeout";
        }
        leaf action {
          type enumeration {
            enum "clear";
            enum "trap";
            enum "restart";
          }
          default "restart";
        }
      }
      container rekey {
        leaf ikeSec {
          type uint32 {
            range "60..604800";
          }
          default "14400";
        }
        leaf espSec {
          type uint32 {
            range "60..604800";
          }
          default "3600";
        }
        leaf espBytes {
          type uint64 {
            range "1..9007199254740991";
          }
        }
        leaf espPackets {
          type uint64 {
            range "1..9007199254740991";
          }
        }
        leaf reauth {
          type boolean;
          default "false";
        }
      }
    }
  }
}
