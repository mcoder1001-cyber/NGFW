NGFW-MIB DEFINITIONS ::= BEGIN

--
-- NGFW private MIB (F-snmp, WBS D7.5): VPP interface counters and agent health, served read-only by the
-- ngfw-agent AgentX subagent (apps/agent/internal/snmpagent).
--
-- PLACEHOLDER OID: ngfwMIB lives under net-snmp's netSnmpPlaypen (1.3.6.1.4.1.8072.9999.9999, "for local
-- experiments") until the product owner registers an IANA Private Enterprise Number. When that happens,
-- change the MODULE-IDENTITY below and snmpagent.NGFWMIBOID together.
--

IMPORTS
    MODULE-IDENTITY, OBJECT-TYPE, Integer32, Counter32, Counter64
        FROM SNMPv2-SMI
    DisplayString, TruthValue
        FROM SNMPv2-TC
    netSnmpPlaypen
        FROM NET-SNMP-MIB;

ngfwMIB MODULE-IDENTITY
    LAST-UPDATED "202609250000Z"
    ORGANIZATION "NGFW project"
    CONTACT-INFO "see docs/user/services/snmp.md"
    DESCRIPTION  "VPP interface counters and ngfw-agent health. Read-only."
    REVISION     "202609250000Z"
    DESCRIPTION  "Initial version (F-snmp); placeholder OID under netSnmpPlaypen."
    ::= { netSnmpPlaypen 7853 }

ngfwAgent   OBJECT IDENTIFIER ::= { ngfwMIB 1 }

ngfwAgentVersion OBJECT-TYPE
    SYNTAX      DisplayString
    MAX-ACCESS  read-only
    STATUS      current
    DESCRIPTION "ngfw-agent version."
    ::= { ngfwAgent 1 }

ngfwVppConnected OBJECT-TYPE
    SYNTAX      TruthValue
    MAX-ACCESS  read-only
    STATUS      current
    DESCRIPTION "true(1) while the agent holds a VPP binary-API connection."
    ::= { ngfwAgent 2 }

ngfwRunningRevision OBJECT-TYPE
    SYNTAX      DisplayString
    MAX-ACCESS  read-only
    STATUS      current
    DESCRIPTION "Transaction id of the last configuration the agent applied."
    ::= { ngfwAgent 3 }

ngfwCommitCounter OBJECT-TYPE
    SYNTAX      Counter32
    MAX-ACCESS  read-only
    STATUS      current
    DESCRIPTION "Applied configuration transactions observed by the subagent (seeded from the agent's
                 persisted history at start)."
    ::= { ngfwAgent 4 }

ngfwAgentDegraded OBJECT-TYPE
    SYNTAX      TruthValue
    MAX-ACCESS  read-only
    STATUS      current
    DESCRIPTION "true(1) when the agent reports DEGRADED (reserved; currently always false(2))."
    ::= { ngfwAgent 5 }

ngfwIfTable OBJECT-TYPE
    SYNTAX      SEQUENCE OF NgfwIfEntry
    MAX-ACCESS  not-accessible
    STATUS      current
    DESCRIPTION "VPP interfaces (not the Linux ones: those are in IF-MIB from net-snmp)."
    ::= { ngfwMIB 2 }

ngfwIfEntry OBJECT-TYPE
    SYNTAX      NgfwIfEntry
    MAX-ACCESS  not-accessible
    STATUS      current
    DESCRIPTION "One VPP interface; the index is sw_if_index + 1."
    INDEX       { ngfwIfIndex }
    ::= { ngfwIfTable 1 }

NgfwIfEntry ::= SEQUENCE {
    ngfwIfIndex        Integer32,
    ngfwIfName         DisplayString,
    ngfwIfAdminStatus  INTEGER,
    ngfwIfOperStatus   INTEGER,
    ngfwIfInOctets     Counter64,
    ngfwIfOutOctets    Counter64,
    ngfwIfInPkts       Counter64,
    ngfwIfOutPkts      Counter64,
    ngfwIfInErrors     Counter64,
    ngfwIfOutErrors    Counter64
}

ngfwIfIndex OBJECT-TYPE
    SYNTAX      Integer32 (1..2147483647)
    MAX-ACCESS  read-only
    STATUS      current
    DESCRIPTION "sw_if_index + 1 (readable for plain walks)."
    ::= { ngfwIfEntry 1 }

ngfwIfName OBJECT-TYPE
    SYNTAX      DisplayString
    MAX-ACCESS  read-only
    STATUS      current
    DESCRIPTION "VPP interface name."
    ::= { ngfwIfEntry 2 }

ngfwIfAdminStatus OBJECT-TYPE
    SYNTAX      INTEGER { up(1), down(2) }
    MAX-ACCESS  read-only
    STATUS      current
    DESCRIPTION "Administrative state."
    ::= { ngfwIfEntry 3 }

ngfwIfOperStatus OBJECT-TYPE
    SYNTAX      INTEGER { up(1), down(2) }
    MAX-ACCESS  read-only
    STATUS      current
    DESCRIPTION "Link state."
    ::= { ngfwIfEntry 4 }

ngfwIfInOctets OBJECT-TYPE
    SYNTAX      Counter64
    MAX-ACCESS  read-only
    STATUS      current
    DESCRIPTION "Received bytes (stats segment /if/rx)."
    ::= { ngfwIfEntry 5 }

ngfwIfOutOctets OBJECT-TYPE
    SYNTAX      Counter64
    MAX-ACCESS  read-only
    STATUS      current
    DESCRIPTION "Transmitted bytes (/if/tx)."
    ::= { ngfwIfEntry 6 }

ngfwIfInPkts OBJECT-TYPE
    SYNTAX      Counter64
    MAX-ACCESS  read-only
    STATUS      current
    DESCRIPTION "Received packets (/if/rx)."
    ::= { ngfwIfEntry 7 }

ngfwIfOutPkts OBJECT-TYPE
    SYNTAX      Counter64
    MAX-ACCESS  read-only
    STATUS      current
    DESCRIPTION "Transmitted packets (/if/tx)."
    ::= { ngfwIfEntry 8 }

ngfwIfInErrors OBJECT-TYPE
    SYNTAX      Counter64
    MAX-ACCESS  read-only
    STATUS      current
    DESCRIPTION "Receive errors (/if/rx-error)."
    ::= { ngfwIfEntry 9 }

ngfwIfOutErrors OBJECT-TYPE
    SYNTAX      Counter64
    MAX-ACCESS  read-only
    STATUS      current
    DESCRIPTION "Transmit errors (/if/tx-error)."
    ::= { ngfwIfEntry 10 }

END
