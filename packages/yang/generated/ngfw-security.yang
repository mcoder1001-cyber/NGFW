module ngfw-security {
  yang-version 1.1;
  namespace "urn:ngfw:security";
  prefix ngfw-security;

  organization "NGFW";
  contact "https://ngfw.dev";
  description "Configuration of the 'security' domain, generated from the NGFW Zod schema (F-restconf-yang).";

  revision 2026-01-01 {
    description "Generated from the NGFW schema.";
  }

  container security {
    description "defensive policy for the box’s own management and control planes";
    container autoBlock {
      description "brute-force / scan detection with automatic temporary blocking via Global Blocking";
      leaf enabled {
        type boolean;
        default "false";
        description "master switch; when off no source is auto-blocked";
      }
      list rules {
        // keyless: no itemKey meta — config lists need a key (documented deviation, RESTCONF orders by index)
        ordered-by user;
        description "one rule per source; a source with no rule is not watched";
        leaf source {
          type enumeration {
            enum "webLogin";
            enum "ssh";
            enum "vpnAuth";
            enum "portScan";
          }
          mandatory true;
          description "webLogin (web/API sign-in), ssh, vpnAuth (IKE/EAP), or portScan (local-in probes)";
        }
        leaf enabled {
          type boolean;
          default "true";
        }
        leaf threshold {
          type uint32 {
            range "1..100000";
          }
          default "5";
          description "failures (portScan: distinct ports) from one source within the window before it is blocked";
        }
        leaf windowSec {
          type uint32 {
            range "1..86400";
          }
          default "60";
          description "the sliding window the threshold is counted over";
        }
        leaf blockSec {
          type uint32 {
            range "1..2592000";
          }
          default "900";
          description "how long a first offence is blocked";
        }
        leaf escalate {
          type boolean;
          default "true";
          description "double the block time on each repeat offence within the memory window, up to the cap";
        }
        leaf maxBlockSec {
          type uint32 {
            range "1..2592000";
          }
          default "86400";
          description "the escalation cap; a single block never lasts longer than this";
        }
      }
      leaf-list allowlist {
        type union {
          type union {
            type string {
              pattern "((25[0-5]|2[0-4][0-9]|1[0-9][0-9]|[1-9][0-9]|[0-9])\\.){3}(25[0-5]|2[0-4][0-9]|1[0-9][0-9]|[1-9][0-9]|[0-9])";
            }
            type string {
              pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))";
            }
          }
          type union {
            type string {
              pattern "((25[0-5]|2[0-4][0-9]|1[0-9][0-9]|[1-9][0-9]|[0-9])\\.){3}(25[0-5]|2[0-4][0-9]|1[0-9][0-9]|[1-9][0-9]|[0-9])/([0-9]|[1-2][0-9]|3[0-2])";
            }
            type string {
              pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))/(12[0-8]|1[01][0-9]|[1-9]?[0-9])";
            }
          }
        }
        description "addresses/networks that are never blocked (your management networks and your own address)";
      }
      leaf maxEntries {
        type uint32 {
          range "1..1000000";
        }
        default "10000";
        description "cap on the live auto-block set; the oldest expiring entry is dropped when it is reached";
      }
      leaf description {
        type string {
          // pattern dropped: not XSD-expressible
          length "0..255";
        }
      }
    }
  }
}
