module vrx-management {
  yang-version 1.1;
  namespace "urn:vrx:management";
  prefix vrx-management;

  import ietf-netconf-acm {
    prefix nacm;
  }

  organization "VRX";
  contact "https://vrx.dev";
  description "Configuration of the 'management' domain, generated from the VRX Zod schema (F-restconf-yang).";

  revision 2026-01-01 {
    description "Generated from the VRX schema.";
  }

  container management {
    description "Local users, AAA, TLS and syslog.";
    list users {
      key "username";
      leaf username {
        type string {
          pattern "[a-z_][a-z0-9_-]{0,31}";
        }
        mandatory true;
      }
      leaf role {
        type enumeration {
          enum "admin";
          enum "operator";
          enum "readonly";
        }
        mandatory true;
        description "admin: everything; operator: edit and commit configuration; readonly: view only";
      }
      leaf scope {
        type string;
        default "*";
        description "role scope; `*` = whole device (tenant scopes are reserved for later)";
      }
      leaf passwordHash {
        type string {
          // pattern dropped: not XSD-expressible
          length "0..512";
        }
        nacm:default-deny-all;
        description "crypt/PHC hash; write-only. A user without a password can only log in with an SSH key";
      }
      leaf-list sshKeys {
        type string {
          // pattern dropped: not XSD-expressible
          length "0..4096";
        }
      }
      leaf fullName {
        type string {
          // pattern dropped: not XSD-expressible
          length "0..255";
        }
      }
      leaf disabled {
        type boolean;
        default "false";
        description "keep the account but refuse logins";
      }
    }
    container aaa {
      leaf-list order {
        type enumeration {
          enum "local";
          enum "radius";
          enum "tacacs";
          enum "ldap";
          enum "oidc";
        }
        description "methods tried in order until one answers; `local` should stay in the list";
      }
      container radius {
        list servers {
          key "address authPort";
          leaf address {
            type union {
              type string {
                pattern "((25[0-5]|2[0-4][0-9]|1[0-9][0-9]|[1-9][0-9]|[0-9])\\.){3}(25[0-5]|2[0-4][0-9]|1[0-9][0-9]|[1-9][0-9]|[0-9])";
              }
              type string {
                pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))";
              }
              type string {
                pattern "[A-Za-z0-9]([A-Za-z0-9-]{0,61}[A-Za-z0-9])?(\\.[A-Za-z0-9]([A-Za-z0-9-]{0,61}[A-Za-z0-9])?)*";
                length "1..253";
              }
            }
            mandatory true;
            description "IP address or hostname";
          }
          leaf authPort {
            type uint32 {
              range "1..65535";
            }
            default "1812";
          }
          leaf acctPort {
            type uint32 {
              range "1..65535";
            }
            default "1813";
          }
          leaf secretRef {
            type string {
              pattern "(psk)/[A-Za-z0-9][A-Za-z0-9_.-]{0,62}";
              length "0..127";
            }
            mandatory true;
            description "reference into the secret store, e.g. psk/radius-primary";
          }
          leaf timeoutSec {
            type uint32 {
              range "1..60";
            }
            default "5";
          }
          leaf vrf {
            type string {
              pattern "[A-Za-z0-9][A-Za-z0-9_.-]*";
              length "1..63";
            }
            default "default";
            description "routing table this object belongs to; `default` is table 0";
          }
        }
      }
      container tacacs {
        list servers {
          key "address port";
          leaf address {
            type union {
              type string {
                pattern "((25[0-5]|2[0-4][0-9]|1[0-9][0-9]|[1-9][0-9]|[0-9])\\.){3}(25[0-5]|2[0-4][0-9]|1[0-9][0-9]|[1-9][0-9]|[0-9])";
              }
              type string {
                pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))";
              }
              type string {
                pattern "[A-Za-z0-9]([A-Za-z0-9-]{0,61}[A-Za-z0-9])?(\\.[A-Za-z0-9]([A-Za-z0-9-]{0,61}[A-Za-z0-9])?)*";
                length "1..253";
              }
            }
            mandatory true;
            description "IP address or hostname";
          }
          leaf port {
            type uint32 {
              range "1..65535";
            }
            default "49";
          }
          leaf secretRef {
            type string {
              pattern "(psk)/[A-Za-z0-9][A-Za-z0-9_.-]{0,62}";
              length "0..127";
            }
            mandatory true;
            description "reference into the secret store, e.g. psk/tacacs-primary";
          }
          leaf timeoutSec {
            type uint32 {
              range "1..60";
            }
            default "5";
          }
          leaf vrf {
            type string {
              pattern "[A-Za-z0-9][A-Za-z0-9_.-]*";
              length "1..63";
            }
            default "default";
            description "routing table this object belongs to; `default` is table 0";
          }
        }
      }
      container ldap {
        list servers {
          key "url";
          leaf url {
            type string {
              // pattern dropped: not XSD-expressible
              length "0..255";
            }
            mandatory true;
            description "ldaps://host:636 (preferred) or ldap://host:389 with StartTLS";
          }
          leaf bindDn {
            type string {
              length "1..255";
            }
            mandatory true;
            description "DN the box binds as to search for the user (a read-only service account)";
          }
          leaf bindPasswordRef {
            type string {
              pattern "(password)/[A-Za-z0-9][A-Za-z0-9_.-]{0,62}";
              length "0..127";
            }
            mandatory true;
            description "password/<name> secret for the bind DN; never the password itself";
          }
          leaf baseDn {
            type string {
              length "1..255";
            }
            mandatory true;
            description "subtree the user search starts from";
          }
          leaf userFilter {
            type string {
              length "1..255";
            }
            default "(uid=%s)";
            description "LDAP filter; %s is replaced with the (escaped) login name, e.g. (uid=%s) or (sAMAccountName=%s)";
          }
          leaf groupAttr {
            type string {
              length "0..64";
            }
            default "memberOf";
            description "attribute on the user entry that lists group DNs (mapped to roles via roleMap)";
          }
          leaf startTls {
            type boolean;
            default "false";
            description "upgrade an ldap:// connection to TLS before binding (not needed for ldaps://)";
          }
        }
      }
      container oidc {
        leaf issuer {
          type string {
            // pattern dropped: not XSD-expressible
            length "0..255";
          }
          mandatory true;
          description "the IdP issuer URL; /.well-known/openid-configuration is read from it";
        }
        leaf clientId {
          type string {
            length "1..255";
          }
          mandatory true;
        }
        leaf clientSecretRef {
          type string {
            pattern "(token)/[A-Za-z0-9][A-Za-z0-9_.-]{0,62}";
            length "0..127";
          }
          mandatory true;
          description "token/<name> secret with the client secret; never the secret itself";
        }
        leaf redirectUri {
          type string {
            // pattern dropped: not XSD-expressible
            length "0..255";
          }
          mandatory true;
          description "registered at the IdP: https://<this box>/api/v1/auth/oidc/callback";
        }
        leaf-list scopes {
          type string {
            pattern "[\\x21\\x23-\\x5b\\x5d-\\x7e]{1,64}";
          }
          description "must include openid";
        }
        leaf usernameClaim {
          type string {
            length "1..64";
          }
          default "preferred_username";
          description "ID-token claim used as the login name";
        }
        leaf roleClaim {
          type string {
            length "1..64";
          }
          default "groups";
          description "ID-token claim listing the user’s groups (mapped to roles via roleMap)";
        }
      }
      list roleMap {
        // keyless: no itemKey meta — config lists need a key (documented deviation, RESTCONF orders by index)
        ordered-by user;
        description "map external groups to local roles; an external user with no mapped group is refused";
        leaf group {
          type string {
            length "1..255";
          }
          mandatory true;
          description "group name or DN from the identity source";
        }
        leaf role {
          type enumeration {
            enum "admin";
            enum "operator";
            enum "readonly";
          }
          mandatory true;
        }
      }
      container mfa {
        leaf required {
          type enumeration {
            enum "none";
            enum "admins";
            enum "all";
          }
          default "none";
          description "none; admins (admin role only); all users";
        }
        leaf issuer {
          type string {
            pattern "[\\x20-\\x7e]+";
            length "0..64";
          }
          default "vrx";
          description "label shown in the authenticator app";
        }
      }
      leaf fallbackLocal {
        type boolean;
        default "true";
        description "allow local-user login when every external server is unreachable";
      }
    }
    container tls {
      leaf certificateRef {
        type string {
          pattern "(cert)/[A-Za-z0-9][A-Za-z0-9_.-]{0,62}";
          length "0..127";
        }
        description "PEM certificate chain in the secret store; absent = self-signed certificate generated on first boot";
      }
      leaf privateKeyRef {
        type string {
          pattern "(key)/[A-Za-z0-9][A-Za-z0-9_.-]{0,62}";
          length "0..127";
        }
        description "matching private key in the secret store";
      }
      leaf minVersion {
        type enumeration {
          enum "1.2";
          enum "1.3";
        }
        default "1.2";
      }
    }
    list syslog {
      key "address port protocol";
      leaf address {
        type union {
          type string {
            pattern "((25[0-5]|2[0-4][0-9]|1[0-9][0-9]|[1-9][0-9]|[0-9])\\.){3}(25[0-5]|2[0-4][0-9]|1[0-9][0-9]|[1-9][0-9]|[0-9])";
          }
          type string {
            pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))";
          }
          type string {
            pattern "[A-Za-z0-9]([A-Za-z0-9-]{0,61}[A-Za-z0-9])?(\\.[A-Za-z0-9]([A-Za-z0-9-]{0,61}[A-Za-z0-9])?)*";
            length "1..253";
          }
        }
        mandatory true;
        description "IP address or hostname";
      }
      leaf port {
        type uint32 {
          range "1..65535";
        }
        default "514";
      }
      leaf protocol {
        type enumeration {
          enum "udp";
          enum "tcp";
          enum "tls";
        }
        default "udp";
      }
      leaf severity {
        type enumeration {
          enum "emergency";
          enum "alert";
          enum "critical";
          enum "error";
          enum "warning";
          enum "notice";
          enum "info";
          enum "debug";
        }
        default "info";
        description "forward messages at this severity and above";
      }
      leaf vrf {
        type string {
          pattern "[A-Za-z0-9][A-Za-z0-9_.-]*";
          length "1..63";
        }
        default "default";
        description "routing table this object belongs to; `default` is table 0";
      }
      leaf-list facilities {
        type enumeration {
          enum "kern";
          enum "user";
          enum "mail";
          enum "daemon";
          enum "auth";
          enum "syslog";
          enum "lpr";
          enum "news";
          enum "uucp";
          enum "cron";
          enum "authpriv";
          enum "ftp";
          enum "local0";
          enum "local1";
          enum "local2";
          enum "local3";
          enum "local4";
          enum "local5";
          enum "local6";
          enum "local7";
        }
        description "Forward only these facilities; empty = all";
      }
      leaf format {
        type enumeration {
          enum "rfc5424";
          enum "rfc3164";
        }
        description "rfc5424 (default; octet-counted over TCP) or the traditional rfc3164 line";
      }
      leaf queueSize {
        type uint32 {
          range "100..1000000";
        }
        description "Messages held while the collector is unreachable (default 10000)";
      }
      container tls {
        description "Required with protocol tls; ignored otherwise (rejected)";
        leaf caRef {
          type string {
            pattern "(cert)/[A-Za-z0-9][A-Za-z0-9_.-]{0,62}";
            length "0..127";
          }
          mandatory true;
          description "Verifies the collector certificate (kind cert)";
        }
        leaf certRef {
          type string {
            pattern "(cert)/[A-Za-z0-9][A-Za-z0-9_.-]{0,62}";
            length "0..127";
          }
          description "Only for collectors that require client authentication; goes with keyRef";
        }
        leaf keyRef {
          type string {
            pattern "(key)/[A-Za-z0-9][A-Za-z0-9_.-]{0,62}";
            length "0..127";
          }
          description "Goes with certRef (kind key)";
        }
        leaf authMode {
          type enumeration {
            enum "x509/name";
            enum "x509/certvalid";
          }
          description "x509/name: certificate valid and its name in permittedPeers (default); x509/certvalid: valid certificate only";
        }
        leaf-list permittedPeers {
          type string {
            pattern "[A-Za-z0-9]([A-Za-z0-9-]{0,61}[A-Za-z0-9])?(\\.[A-Za-z0-9]([A-Za-z0-9-]{0,61}[A-Za-z0-9])?)*";
            length "1..253";
          }
          description "Collector certificate names accepted with x509/name; empty = the collector host name";
        }
      }
    }
    container prometheus {
      leaf enabled {
        type boolean;
        default "false";
        description "open an external Prometheus listener (the loopback /metrics endpoint is always on)";
      }
      leaf listen {
        type union {
          type string {
            pattern "((25[0-5]|2[0-4][0-9]|1[0-9][0-9]|[1-9][0-9]|[0-9])\\.){3}(25[0-5]|2[0-4][0-9]|1[0-9][0-9]|[1-9][0-9]|[0-9])";
          }
          type string {
            pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))";
          }
        }
        default "0.0.0.0";
        description "address the external /metrics listener binds to";
      }
      leaf port {
        type uint32 {
          range "1..65535";
        }
        default "9101";
      }
      leaf-list allow {
        type string {
          length "0..49";
        }
        description "CIDRs allowed to scrape (empty = allow any source that reaches the listener)";
      }
    }
    container alarms {
      list rules {
        key "name";
        leaf name {
          type string;
          description "The map key.";
        }
        leaf metric {
          type enumeration {
            enum "interface_rx_bps";
            enum "interface_tx_bps";
            enum "interface_rx_drops";
            enum "interface_tx_drops";
            enum "interface_link_down";
            enum "worker_cpu_percent";
            enum "buffer_used_percent";
            enum "node_error_rate";
          }
          mandatory true;
        }
        leaf op {
          type enumeration {
            enum "gt";
            enum "ge";
            enum "lt";
            enum "le";
            enum "eq";
          }
          default "gt";
          description "gt > · ge ≥ · lt < · le ≤ · eq =";
        }
        leaf threshold {
          type decimal64 {
            fraction-digits 6;
          }
          mandatory true;
          description "compared against the metric (bps, drops/s, percent, or 1/0 for link_down)";
        }
        leaf forSec {
          type uint32 {
            range "0..86400";
          }
          default "0";
          description "the condition must hold this long before the alarm is raised (hysteresis); 0 = immediately";
        }
        leaf severity {
          type enumeration {
            enum "info";
            enum "warning";
            enum "critical";
          }
          default "warning";
        }
        leaf interface {
          type string {
            length "0..63";
          }
          description "limit an interface metric to this interface; empty = every interface";
        }
        leaf description {
          type string {
            // pattern dropped: not XSD-expressible
            length "0..255";
          }
        }
        leaf enabled {
          type boolean;
          default "true";
        }
        leaf-list targets {
          type string {
            pattern "[A-Za-z0-9][A-Za-z0-9_.-]*";
            length "1..63";
          }
          description "names of management.alarms.targets to notify on raise and clear; empty = record only";
        }
      }
      list targets {
        key "name";
        leaf name {
          type string;
          description "The map key.";
        }
      }
    }
    container notifications {
      list channels {
        // keyless: no itemKey meta — config lists need a key (documented deviation, RESTCONF orders by index)
        ordered-by user;
        leaf name {
          type string {
            pattern "[A-Za-z0-9][A-Za-z0-9_.-]*";
            length "1..63";
          }
          mandatory true;
        }
        leaf enabled {
          type boolean;
          default "true";
        }
        leaf vrf {
          type string;
          default "default";
          description "Only default API namespace routing is supported; other VRFs fail validation.";
        }
        leaf type {
          type enumeration {
            enum "email";
            enum "webhook";
          }
          mandatory true;
        }
        container email {
          leaf smtpHost {
            type union {
              type string {
                pattern "((25[0-5]|2[0-4][0-9]|1[0-9][0-9]|[1-9][0-9]|[0-9])\\.){3}(25[0-5]|2[0-4][0-9]|1[0-9][0-9]|[1-9][0-9]|[0-9])";
              }
              type string {
                pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))";
              }
              type string {
                pattern "[A-Za-z0-9]([A-Za-z0-9-]{0,61}[A-Za-z0-9])?(\\.[A-Za-z0-9]([A-Za-z0-9-]{0,61}[A-Za-z0-9])?)*";
                length "1..253";
              }
            }
            mandatory true;
            description "IP address or hostname";
          }
          leaf port {
            type uint32 {
              range "1..65535";
            }
            default "587";
          }
          leaf tls {
            type enumeration {
              enum "starttls";
              enum "tls";
            }
            default "starttls";
          }
          leaf username {
            type string {
              // pattern dropped: not XSD-expressible
              length "1..254";
            }
          }
          leaf passwordRef {
            type string {
              pattern "(password)/[A-Za-z0-9][A-Za-z0-9_.-]{0,62}";
              length "0..127";
            }
            description "reference to a stored secret of kind password";
          }
          leaf from {
            type string {
              pattern "([A-Za-z0-9_'+\\-]+\\.)*[A-Za-z0-9_'+\\-]*[A-Za-z0-9_+-]@([A-Za-z0-9][A-Za-z0-9\\-]*\\.)+[A-Za-z]{2,}";
              length "0..254";
            }
            mandatory true;
          }
          leaf-list to {
            type string {
              pattern "([A-Za-z0-9_'+\\-]+\\.)*[A-Za-z0-9_'+\\-]*[A-Za-z0-9_+-]@([A-Za-z0-9][A-Za-z0-9\\-]*\\.)+[A-Za-z]{2,}";
              length "0..254";
            }
          }
        }
        container webhook {
          leaf url {
            type string {
              length "0..2048";
            }
            mandatory true;
          }
          leaf secretRef {
            type string {
              pattern "(token)/[A-Za-z0-9][A-Za-z0-9_.-]{0,62}";
              length "0..127";
            }
            mandatory true;
            description "reference to a stored secret of kind token";
          }
        }
      }
      list rules {
        // keyless: no itemKey meta — config lists need a key (documented deviation, RESTCONF orders by index)
        ordered-by user;
        leaf name {
          type string {
            pattern "[A-Za-z0-9][A-Za-z0-9_.-]*";
            length "1..63";
          }
          mandatory true;
        }
        leaf enabled {
          type boolean;
          default "true";
        }
        leaf-list events {
          type enumeration {
            enum "alarm";
            enum "commit";
            enum "link";
            enum "vpn";
            enum "global-blocking";
          }
        }
        leaf minSeverity {
          type enumeration {
            enum "info";
            enum "warning";
            enum "critical";
          }
          default "warning";
        }
        leaf-list channels {
          type string {
            pattern "[A-Za-z0-9][A-Za-z0-9_.-]*";
            length "1..63";
          }
        }
        leaf throttleSec {
          type uint32 {
            range "1..86400";
          }
          default "60";
        }
      }
    }
  }
}
