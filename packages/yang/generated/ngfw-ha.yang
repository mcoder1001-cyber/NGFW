module ngfw-ha {
  yang-version 1.1;
  namespace "urn:ngfw:ha";
  prefix ngfw-ha;

  organization "NGFW";
  contact "https://ngfw.dev";
  description "Configuration of the 'ha' domain, generated from the NGFW Zod schema (F-restconf-yang).";

  revision 2026-01-01 {
    description "Generated from the NGFW schema.";
  }

  container ha {
    description "VRRPv3 virtual routers (VPP plugin or keepalived) and cluster membership / config sync.";
    list vrrp {
      key "name";
      leaf name {
        type string;
        description "The map key.";
      }
      description "Keyed by name; a virtual router is (interface, address family, VRID) on the wire";
      leaf enabled {
        type boolean;
        default "true";
      }
      leaf description {
        type string {
          // pattern dropped: not XSD-expressible
          length "0..255";
        }
      }
      leaf interface {
        type string {
          pattern "[A-Za-z][A-Za-z0-9_-]*(/[0-9a-fA-F]+)*(\\.[0-9]+)?";
          length "1..63";
        }
        mandatory true;
        description "Interface the virtual router runs on";
      }
      leaf vrId {
        type uint32 {
          range "1..255";
        }
        mandatory true;
        description "Virtual router id, unique per interface and address family";
      }
      leaf addressFamily {
        type enumeration {
          enum "ipv4";
          enum "ipv6";
        }
        default "ipv4";
      }
      leaf priority {
        type uint32 {
          range "1..255";
        }
        default "100";
        description "255 = address owner";
      }
      leaf advertisementIntervalMs {
        type uint32 {
          range "10..40950";
        }
        default "1000";
        description "Multiple of 10 ms (VRRPv3 centiseconds)";
      }
      leaf preempt {
        type boolean;
        default "true";
      }
      leaf acceptMode {
        type boolean;
        default "false";
        description "Master accepts packets addressed to the virtual addresses it does not own";
      }
      container unicast {
        description "Omit for multicast advertisements";
        leaf-list peers {
          type union {
            type string {
              pattern "((25[0-5]|2[0-4][0-9]|1[0-9][0-9]|[1-9][0-9]|[0-9])\\.){3}(25[0-5]|2[0-4][0-9]|1[0-9][0-9]|[1-9][0-9]|[0-9])";
            }
            type string {
              pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))";
            }
          }
        }
      }
      leaf-list addresses {
        type union {
          type string {
            pattern "((25[0-5]|2[0-4][0-9]|1[0-9][0-9]|[1-9][0-9]|[0-9])\\.){3}(25[0-5]|2[0-4][0-9]|1[0-9][0-9]|[1-9][0-9]|[0-9])";
          }
          type string {
            pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))";
          }
        }
        description "Same address family as the virtual router";
      }
      leaf vrf {
        type string {
          pattern "[A-Za-z0-9][A-Za-z0-9_.-]*";
          length "1..63";
        }
        default "default";
        description "Routing table this object belongs to (first-class, never implicit)";
      }
      leaf engine {
        type enumeration {
          enum "vpp";
          enum "keepalived";
        }
        default "vpp";
        description "Native engine vrrp plugin or keepalived";
      }
      list track {
        // keyless: no itemKey meta — config lists need a key (documented deviation, RESTCONF orders by index)
        ordered-by user;
        leaf interface {
          type string {
            pattern "[A-Za-z][A-Za-z0-9_-]*(/[0-9a-fA-F]+)*(\\.[0-9]+)?";
            length "1..63";
          }
          mandatory true;
        }
        leaf priorityDecrement {
          type uint32 {
            range "1..253";
          }
          default "10";
          description "Subtracted from the priority while the tracked interface is down";
        }
      }
    }
    container cluster {
      leaf enabled {
        type boolean;
        default "false";
      }
      leaf nodeName {
        type string {
          pattern "[A-Za-z0-9]([A-Za-z0-9-]{0,61}[A-Za-z0-9])?(\\.[A-Za-z0-9]([A-Za-z0-9-]{0,61}[A-Za-z0-9])?)*";
          length "1..253";
        }
        mandatory true;
        description "Name of this member";
      }
      list peers {
        // keyless: no itemKey meta — config lists need a key (documented deviation, RESTCONF orders by index)
        ordered-by user;
        leaf name {
          type string {
            pattern "[A-Za-z0-9]([A-Za-z0-9-]{0,61}[A-Za-z0-9])?(\\.[A-Za-z0-9]([A-Za-z0-9-]{0,61}[A-Za-z0-9])?)*";
            length "1..253";
          }
          mandatory true;
        }
        leaf address {
          type union {
            type string {
              pattern "((25[0-5]|2[0-4][0-9]|1[0-9][0-9]|[1-9][0-9]|[0-9])\\.){3}(25[0-5]|2[0-4][0-9]|1[0-9][0-9]|[1-9][0-9]|[0-9])";
            }
            type string {
              pattern "(([0-9a-fA-F]{1,4}:){7}[0-9a-fA-F]{1,4}|([0-9a-fA-F]{1,4}:){1,7}:|([0-9a-fA-F]{1,4}:){1,6}:[0-9a-fA-F]{1,4}|([0-9a-fA-F]{1,4}:){1,5}(:[0-9a-fA-F]{1,4}){1,2}|([0-9a-fA-F]{1,4}:){1,4}(:[0-9a-fA-F]{1,4}){1,3}|([0-9a-fA-F]{1,4}:){1,3}(:[0-9a-fA-F]{1,4}){1,4}|([0-9a-fA-F]{1,4}:){1,2}(:[0-9a-fA-F]{1,4}){1,5}|[0-9a-fA-F]{1,4}:((:[0-9a-fA-F]{1,4}){1,6})|:((:[0-9a-fA-F]{1,4}){1,7}|:))";
            }
          }
          mandatory true;
        }
        leaf certificatePin {
          type string {
            pattern "[a-f0-9]{64}";
          }
        }
      }
      leaf port {
        type uint32 {
          range "1..65535";
        }
        default "4370";
      }
      leaf secretRef {
        type string {
          pattern "(key)/[A-Za-z0-9][A-Za-z0-9_.-]{0,62}";
          length "1..127";
        }
        mandatory true;
        description "Shared key protecting the sync channel; stored through POST /api/v1/secrets (kind key)";
      }
      leaf interface {
        type string {
          pattern "[A-Za-z][A-Za-z0-9_-]*(/[0-9a-fA-F]+)*(\\.[0-9]+)?";
          length "1..63";
        }
        description "Interface carrying the cluster traffic (optional, informational for the renderer)";
      }
      leaf vrf {
        type string {
          pattern "[A-Za-z0-9][A-Za-z0-9_.-]*";
          length "1..63";
        }
        default "default";
        description "Routing table this object belongs to (first-class, never implicit)";
      }
      leaf configSync {
        type boolean;
        default "true";
      }
      container stateSync {
        leaf nat {
          type boolean;
          default "false";
        }
        leaf ipsec {
          type boolean;
          default "false";
        }
        leaf acl {
          type boolean;
          default "false";
        }
        container natListener {
          leaf address {
            type string {
              pattern "((25[0-5]|2[0-4][0-9]|1[0-9][0-9]|[1-9][0-9]|[0-9])\\.){3}(25[0-5]|2[0-4][0-9]|1[0-9][0-9]|[1-9][0-9]|[0-9])";
            }
            mandatory true;
          }
          leaf port {
            type uint32 {
              range "1..65535";
            }
            default "8750";
          }
          leaf pathMtu {
            type uint32 {
              range "576..9000";
            }
            default "1500";
          }
        }
        container natFailover {
          leaf address {
            type string {
              pattern "((25[0-5]|2[0-4][0-9]|1[0-9][0-9]|[1-9][0-9]|[0-9])\\.){3}(25[0-5]|2[0-4][0-9]|1[0-9][0-9]|[1-9][0-9]|[0-9])";
            }
            mandatory true;
          }
          leaf port {
            type uint32 {
              range "1..65535";
            }
            default "8750";
          }
          leaf sessionRefreshSec {
            type uint32 {
              range "1..3600";
            }
            default "10";
          }
        }
      }
      leaf-list syncExclude {
        type string; // pattern dropped: not XSD-expressible
      }
    }
  }
}
